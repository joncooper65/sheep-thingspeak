FME workspace conwyMetData.fmw

Parameters:
- since = 2015-11-18T23:30:00   # Since
- SourceDataset_CSV = /conwy-met-station/*.dat   # Source CSV (CommaSeparatedValue) File(s)
- DestDataset_JSON = e:\out.json   # Destination JSON (JavaScript Object Notation) File

Readers:
- CSV_1: CSV from $(SourceDataset_CSV)

Writers:
- JSON_1: JSON to $(DestDataset_JSON)

CSV (reader CSV_1)
    attributes: col0 char(20), col1 number(5,3), col2 number(6,1), col3 number(5,2), col4 number(5,3), col5 number(5,2), col6 number(8,4), col7 number(5,2), col8 number(5,3), col9 number(5,3), col10 number(5,3), col11 number(5,3), col12 number(5,3), col13 number(6,2), col14 number(7,3), col15 number(6,2), col16 number(7,3), col17 number(8,3), col18 number(7,3), col19 number(7,2), col20 number(7,2), col21 number(7,2), col22 number(7,2), col23 number(7,2), col24 number(5,2), col25 number(5,2), col26 number(4,2), col27 number(2,0), col28 number(4,1), col29 number(5,2)
    -> Attribute_Name
Attribute_Name: AttributeRenamer
    ATTR_LIST = col0,TIMESTAMP,,col1,WS,,col2,WD,,col3,WD_Std,,col4,WS_Std,,col5,Ta_Avg,,col6,Pa_Avg,,col7,Rh_Avg,,col8,Q_Avg,,col9,Ta_Std,,col10,Pa_Std,,col11,Rh_Std,,col12,Q_Std,,col13,NR_Avg,,col14,NR_Std,,col15,NR_Corrected_Avg,,col16,NR_Corrected_Std,,col17,SWin_Avg,,col18,SWin_Std,,col19,STP_TSoil50_Avg,,col20,STP_TSoil20_Avg,,col21,STP_TSoil10_Avg,,col22,STP_TSoil5_Avg,,col23,STP_TSoil2_Avg,,col24,TDT1_VWC10,,col25,TDT1_TSoil10,,col26,TDT1_SoilPerm10,,col27,TDT1_SoilEC10,,col28,Rain_Tot,,col29,batt_volt_Min,
    -> Format_Timestamp
Format_Timestamp: DateFormatter
    DATE_ATTR = TIMESTAMP
    FMT = ISO DateTime (%Y-%m-%dT%H:%M:%S)
    SRCFMT = %Y-%m-%d %H:%M:%S
    INVALID_DATE_VALUE = _FME_NO_OP_
    -> Date_Filter
Date_Filter: Tester
    TEST_MODE = Automatic
    TEST_CLAUSE = TEST @Value(TIMESTAMP) > $(since)
    TEST_DESCRIPTION = ""
    BOOL_OP = OR
    PASSED -> Order_By_Time
Order_By_Time: Sorter
    SORT_PARM = TIMESTAMP ALPHA ASCENDING
    SORTED -> JSON (writer JSON_1)
JSON (writer JSON_1)
    attributes: TIMESTAMP string, WS string, WD string, WD_Std string, WS_Std string, Ta_Avg string, Pa_Avg string, Rh_Avg string, Q_Avg string, Ta_Std string, Pa_Std string, Rh_Std string, Q_Std string, NR_Avg string, NR_Std string, NR_Corrected_Avg string, NR_Corrected_Std string, SWin_Avg string, SWin_Std string, STP_TSoil50_Avg string, STP_TSoil20_Avg string, STP_TSoil10_Avg string, STP_TSoil5_Avg string, STP_TSoil2_Avg string, TDT1_VWC10 string, TDT1_TSoil10 string, TDT1_SoilPerm10 string, TDT1_SoilEC10 string, Rain_Tot string, batt_volt_Min string
